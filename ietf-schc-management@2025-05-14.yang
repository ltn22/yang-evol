module ietf-schc-management {
  yang-version 1.1;
  namespace "urn:ietf:params:xml:ns:yang:ietf-schc-management";
  prefix schc-mngt;

  import ietf-schc {
      prefix schc;
  }

  organization
    "IETF Static Context Header Compression (SCHC) working group";
  contact
    "WG Web:   <https://datatracker.ietf.org/wg/schc/about/>
     WG List:  <mailto:schc@ietf.org>
     Editor:   Laurent Toutain
       <mailto:laurent.toutain@imt-atlantique.fr>
     Editor:   Ana Minaburo
       <mailto:ana.minaburo@gmail.com>";
  description
     "
     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     *************************************************************************

     This module extends the ietf-schc module to include the compound-ack 
     behavior for Ack On Error as defined in RFC YYYY. 
     It introduces a new leaf for Ack on Error defining the format of the
     SCHC Ack and add the possibility to send several bitmaps in a single 
     answer.";

  revision 2025-05-14 {
    description
      "Initial version for RFC YYYY ";
    reference
      "RFC YYYY: OAM";
  }

  identity nature-management {
    base schc:nature-base-type;
    description 
      "Compression/Decompression rule used for managing context";
  }

  feature management {
    description
      "SCHC compression capabilities for rule management.";
  }

  grouping management-content {
    description 
      "This group contains parameters to control management procedure.";

    container guard-period {
      leaf ticks-duration {
        type uint8;
        default "20";
        description
          "Duration of one tick in microseconds:
              2^ticks-duration/10^6 = 1.048s.";
      }
      leaf ticks-numbers {
        type uint16 {
          range "0..max";
        }
        description
          "Timer duration = ticks-numbers*2^ticks-duration / 10^6.";
      }
    }
  }

  augment "/schc:schc/schc:rule/schc:nature" {
    case management {
          if-feature "management";
          uses management-content;
    }
  }


  rpc duplicate-rule {
        input {
          container from {
            uses schc:rule-id-type;
            mandatory true;
            description 
              "Orign Rule ID";
          }
          container to {
            uses schc:rule-id-type;
            mandatory true;
            description
              "Destination Rule ID";
          }
          leaf ipatch-sequence {
            type binary;

            description 
              "CBOR sequence for an CORECONF iPatch used to modify the 
               newly created Rule.
               This parameter is optional, and set by default to 0xF6 (CBOR null)";
          }
        }
        output {
          leaf status {
            type string;
            description 
              "Return the status of the RPC. TO BE DEFINED MORE PRECISELY";
          }
        }
        description 
          "This RPC duplicate a rule, from a existing one given in leaf 'from' to a new
          non existing rule defined by 'to'. The content of the new rule may be updated
          with a iPatch, where the CORECONF payload contained in 'ipatch-sequence'.";
      }
}
